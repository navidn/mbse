# RequirmentTable

## 2: Modify Order (Functional)
The platform shall allow users to add / remove products from order before payment

## 4: Compatibility Mobile (Functional)
The platform shall be compatible with mobile device (Android & IOS).

## 5: Compatibility Desktop (Functional)
The platform shall be compatible with PC (Windows and MacOS).

## 6: Search Bar (Functional)
The platform shall have search bar for user to search stores / products.

## 7: Customer Support (Functional)
The platform shall have customer support include Live Chat, FAQ sections and Order Help include Cancel Order and Refund.

## 8: Subscribe Notification (Functional)
The platform shall allow users to subscribe stores discount notifications through email.

## 9: Modify Menu Products (Functional)
The Platform shall allow merchants to add / remove products from menus.

## 10: Modify Product Price (Functional)
The Platform shall allow merchants to set / change price for each product from menus.

## 11: Modify Product Description (Functional)
The Platform shall allow merchants to add / edit products description include food ingredient list & total numbers of the product.

## 12: Modify Product Image (Functional)
The Platform shall allow merchants to add / edit front & back photographs of products.

## 13: Availability (Functional)
The platform shall be available 22 ± 2 hours a day in the USA by 2025.

## 3: Tracking Order (Functional)
The Platform shall track the order though GPS system.

## 14: Account Creation (Functional)
The platform shall allow users to create maximum of 2 accounts by using the same phone number / email address.

## 15: Account Update (Functional)
The platform shall allow users to update account information include Phone Number, Home Address, Nickname, Payment Methods.

## 16: Account Management (Functional)
The platform shall allow users to management account include Membership, Platform Setting, Notification, Favourite Store.

## 17: Login Authentication (Functional)
The platform shall have secure login authentication mechanism by sending code through text messages / email to verify authentication.

## 18: Transaction Time (Functional)
The platform shall process the transaction time in 10s ± 5s from the time the order was placed.

## 19: Up / Down Time (Functional)
The platform shall have uptime 166 hours, 98% time of a week. Downtime shall have 2 hours, 2% time of a week at night on PST.

## 20: Product Element (Functional)
The interface shall include the product elements include food ingredient list & total numbers of the product as product description.

## 21: Product Image (Functional)
The interface shall include with front & back photographs of products.

## 22: Menu Stores (Functional)
The platform shall have at least 1 menu from the cooperative stores.

## 23: Cart Limit (Functional)
The platform shall allow users to add maximum of 9999 product numbers into cart.

## 24: Product Recommendation (Functional)
A dynamic product recommendation system shall be deployed by the platform to recommend new offerings from merchants to customers in a timeframe of every 168 hours.

## 25: Discount (Functional)
The platform shall include discounts for customer orders to customers through a membership system.

## 26: Order Management Limit (Functional)
The platform shall allow users to add / remove products within 10 minutes of placing the order.

## 27: Feedback (Functional)
The platform shall allow customer to leave comments and 1 to 5 stars feedback for products from cooperate stores.

## 28: Online Payment Methods (Functional)
The platform shall support multiple payment methods: Credit Card, Debit Card, PayPal, Venmo, Alipay, WeChat Pay, Apple Pay.

## 29: Gift Card Payment (Functional)
The Platform shall support platform gift card as payment method.

## 30: Incentive Plan (Informational)
The platform shall have the incentive plan for delivery personnel to increase express revenue.

## 31: Partnership (Informational)
The platform shall establish partnerships with 10,000 ± 1000 merchants in California by 2025.

## 1: Review Order (Functional)
| The platform shall allow users to review current order with price of each product / product quantity / total price before the order. |
| --- |
