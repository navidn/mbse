# Fly_By_Wire_Requirements

## Requirements!Requirements: References to Requirements.xlsx (Requirements) (Container)
Read-only references to Microsoft Excel document.
- srcFileChecksum: 39FD88C110E0AA0B4C556D376AC56A3B

### 1: The Flight Control System components shall be no more than 786 lbs. (Functional)

### 2: The Flight Control System hydraulic actuators shall be designed to operate to the flow state: (Functional)
The Flight Control System hydraulic actuators shall be designed to operate to the flow state:
Supply: 3000 +/- 50 PSI
Return 0 to 50 PSI

### 3: The Flight Control system shall provide augmentation of pilot cockpit commands during manual AND automatic flight. (Functional)

### 4: The Flight Control system shall manually disengage the autopilot function when manually commanded by the pilot. [14 CFR Part 25] (Functional)

### 5: The Flight Control System shall control and maneuver the aircraft during [14 CFR Part 25]: (Functional)
The Flight Control System shall control and maneuver the aircraft during [14 CFR Part 25]:
- Takeoff
- Climb
- Level flight
- Descent
- Landing

### 6: The Aileron surface shall be right wing down when cockpit controls are turned right (clockwise) (Functional)
The Aileron surface shall be right wing down when cockpit controls are turned right (clockwise)
[14 CFR Part 25]

### 7: The Aileron surface shall be left wing down when cockpit controls are turned left (couterclockwise) (Functional)

### 8: The elevator surface shall be nose up when cockpit controls are set to rearward (Functional)
The elevator surface shall be nose up when cockpit controls are set to rearward
[14 CFR Part 25]

### 9: The Flight Control System shall maintain flight should the engines fail. (Functional)
The Flight Control System shall maintain flight should the engines fail.
[14 CFR Part 25]

### 10: The Primary Flight Control Computer shall complete system initialization in less than 5 minutes 40 seconds following a power on procedure on ground, in air or during an electrical power outage. (Functional)
The Primary Flight Control Computer shall complete system initialization in less than 5 minutes 40 seconds following a power on procedure on ground, in air or during an electrical power outage.
[14 CFR Part 25]

### 11: The Flight Control Computer shall be powered by 28 VDC ± 0.5 VDC in accordance with the statement of work. (Functional)

### 12: The Flight Control System shall have mechanical stops that will limit the range of motion of each movable aerodynamic surface controlled by the system. (Functional)
The Flight Control System shall have mechanical stops that will limit the range of motion of each movable aerodynamic surface controlled by the system.
[14 CFR Part 25]

### 13: The Flight Control Computer shall receive control surface position via sensor data. (Functional)

### 14: The Flight Control system shall be operational 5 years after award of initial contract. (Functional)

### 15: he Flight Control System shall be constructed and fully operational 5 years from the date of the initial contract award. (Functional)

### 16: The Flight Control System shall have a service life of 98,0000 flight hours. (Functional)

### 17: The Flight Control System shall have a service life of 20 years. (Functional)

### 18: The Flight Control System shall have a reliability of 99.9%. (Functional)

### 19: No significant safety failure shall be carried out in service for a period greater than 6 years. (Functional)

### 20: All Flight control components shall be capable of being readily installed, removed, or replaced without alterations, misalignment or damage to the items being installed. (Functional)

### 21: The flight control system components shall have maintenance intervals as follows: (Functional)
The flight control system components shall have maintenance intervals as follows:
• A Check = 850 hours
• C Check = 8500 hours
